module c {
  yang-version 1.1;

  prefix c;
  namespace "http://example.com/c/";

  revision 2026-04-02;

  feature c-feature;
  feature c-feature-impl;

  identity c-identity;

  leaf simple {
    type uint8;
  }

  grouping items {
    leaf x {
      type int32; 
    }
    leaf y {
      type int32;
    }
  }
}
